"""Folder Watch Python Agent for FreeCAD.

Run this macro once inside the FreeCAD GUI. It watches the local inbox folder
for JSON jobs, executes the referenced Python script, and writes screenshots,
exports, and a result.json file to the out folder.
"""

import json
import os
import shutil
import struct
import sys
import time
import traceback
import zlib
from pathlib import Path

import FreeCAD as App

try:
    import FreeCADGui as Gui
except Exception:
    Gui = None


DEFAULT_ROOT = Path.cwd()
POLL_INTERVAL_MS = 1000
AGENT_DOCUMENT_COMMENT_PREFIX = "freecad_folder_watch_agent:"
AGENT_SESSION_PREFIX = AGENT_DOCUMENT_COMMENT_PREFIX + "session="
AGENT_PROJECT_SESSION_PREFIX = AGENT_DOCUMENT_COMMENT_PREFIX + "project_session="
BRIDGE_VERSION = "0.6.1-detect-blank-screenshots"


def _import_qtcore():
    for module_name in ("PySide6", "PySide2", "PySide"):
        try:
            module = __import__(module_name, fromlist=["QtCore"])
            return module.QtCore
        except Exception:
            pass
    raise RuntimeError("Could not import QtCore from PySide6, PySide2, or PySide")


def _macro_root():
    env_root = os.environ.get("FREECAD_AGENT_ROOT")
    if env_root:
        return Path(env_root).expanduser().resolve()

    try:
        return Path(__file__).resolve().parent
    except Exception:
        return DEFAULT_ROOT


def _safe_name(value):
    cleaned = []
    for char in str(value):
        if char.isalnum() or char in ("-", "_"):
            cleaned.append(char)
        else:
            cleaned.append("_")
    name = "".join(cleaned).strip("_")
    return name or "freecad_agent_job"


def _freecad_internal_name(value):
    name = _safe_name(value).replace("-", "_")
    if not name[0].isalpha():
        name = "Job_{}".format(name)
    return name


def _session_id(value):
    return _safe_name(value or "default")


def _project_id(value):
    return _safe_name(value or "default")


def _now_iso():
    return time.strftime("%Y-%m-%dT%H:%M:%S%z")


def _read_json(path, default):
    try:
        return json.loads(path.read_text(encoding="utf-8"))
    except Exception:
        return default


def _write_json(path, payload):
    path.parent.mkdir(parents=True, exist_ok=True)
    tmp_path = path.with_suffix(path.suffix + ".tmp")
    tmp_path.write_text(json.dumps(payload, indent=2, sort_keys=True), encoding="utf-8")
    tmp_path.replace(path)


def _append_jsonl(path, payload):
    path.parent.mkdir(parents=True, exist_ok=True)
    with path.open("a", encoding="utf-8") as jsonl_file:
        jsonl_file.write(json.dumps(payload, sort_keys=True))
        jsonl_file.write("\n")


def _agent_document_name(project, session):
    if project == "default":
        return _freecad_internal_name("Agent_{}".format(session))
    return _freecad_internal_name("Agent_{}_{}".format(project, session))


def _agent_document_label(project, session):
    if project == "default":
        return "Agent {}".format(session)
    return "Agent {} / {}".format(project, session)


def _session_marker(project, session):
    return "{}{}/{}".format(AGENT_PROJECT_SESSION_PREFIX, project, session)


def _legacy_session_marker(session):
    return "{}{}".format(AGENT_SESSION_PREFIX, session)


def _shape_objects(doc, visible_only=False):
    objects = []
    for obj in getattr(doc, "Objects", []):
        if visible_only:
            try:
                if not obj.ViewObject.Visibility:
                    continue
            except Exception:
                pass
        shape = getattr(obj, "Shape", None)
        if shape is not None and not getattr(shape, "isNull", lambda: True)():
            objects.append(obj)
    return objects


def _bounding_box_dict(bound_box):
    return {
        "x_min": bound_box.XMin,
        "x_max": bound_box.XMax,
        "y_min": bound_box.YMin,
        "y_max": bound_box.YMax,
        "z_min": bound_box.ZMin,
        "z_max": bound_box.ZMax,
        "x_length": bound_box.XLength,
        "y_length": bound_box.YLength,
        "z_length": bound_box.ZLength,
    }


def _round_number(value):
    try:
        return round(float(value), 3)
    except Exception:
        return value


def _compact_bounding_box(box):
    if not box:
        return None
    return {
        "size": [
            _round_number(box.get("x_length", 0.0)),
            _round_number(box.get("y_length", 0.0)),
            _round_number(box.get("z_length", 0.0)),
        ],
        "min": [
            _round_number(box.get("x_min", 0.0)),
            _round_number(box.get("y_min", 0.0)),
            _round_number(box.get("z_min", 0.0)),
        ],
        "max": [
            _round_number(box.get("x_max", 0.0)),
            _round_number(box.get("y_max", 0.0)),
            _round_number(box.get("z_max", 0.0)),
        ],
    }


def _union_bounding_box(objects):
    boxes = [obj.get("bounding_box") for obj in objects if obj.get("bounding_box")]
    if not boxes:
        return None
    return {
        "x_min": min(box["x_min"] for box in boxes),
        "x_max": max(box["x_max"] for box in boxes),
        "y_min": min(box["y_min"] for box in boxes),
        "y_max": max(box["y_max"] for box in boxes),
        "z_min": min(box["z_min"] for box in boxes),
        "z_max": max(box["z_max"] for box in boxes),
        "x_length": max(box["x_max"] for box in boxes)
        - min(box["x_min"] for box in boxes),
        "y_length": max(box["y_max"] for box in boxes)
        - min(box["y_min"] for box in boxes),
        "z_length": max(box["z_max"] for box in boxes)
        - min(box["z_min"] for box in boxes),
    }


def _document_info(doc):
    objects = []
    for obj in getattr(doc, "Objects", []):
        entry = {
            "name": getattr(obj, "Name", ""),
            "label": getattr(obj, "Label", ""),
            "type_id": getattr(obj, "TypeId", ""),
        }
        try:
            entry["visible"] = bool(obj.ViewObject.Visibility)
        except Exception:
            entry["visible"] = None
        shape = getattr(obj, "Shape", None)
        if shape is not None and not getattr(shape, "isNull", lambda: True)():
            try:
                entry["bounding_box"] = _bounding_box_dict(shape.BoundBox)
                entry["volume"] = float(getattr(shape, "Volume", 0.0))
                entry["area"] = float(getattr(shape, "Area", 0.0))
            except Exception as exc:
                entry["shape_error"] = str(exc)
        objects.append(entry)

    return {
        "name": getattr(doc, "Name", ""),
        "label": getattr(doc, "Label", ""),
        "object_count": len(objects),
        "objects": objects,
    }


def _screenshot_summary(screenshot):
    if isinstance(screenshot, dict):
        path = screenshot.get("path")
        summary = {
            "view": screenshot.get("view") or (Path(path).stem if path else None),
            "path": path,
        }
        if screenshot.get("error"):
            summary["error"] = screenshot.get("error")
        return summary
    path = str(screenshot)
    return {"view": Path(path).stem, "path": path}


def _result_summary(result, max_objects=30):
    document = result.get("document") or {}
    objects = document.get("objects") or []
    visible_objects = [
        obj for obj in objects if obj.get("visible") is not False and obj.get("bounding_box")
    ]
    object_source = visible_objects or [obj for obj in objects if obj.get("bounding_box")]

    compact_objects = []
    for obj in object_source[:max_objects]:
        compact_objects.append(
            {
                "name": obj.get("name"),
                "label": obj.get("label"),
                "type_id": obj.get("type_id"),
                "size": (_compact_bounding_box(obj.get("bounding_box")) or {}).get("size"),
                "volume": _round_number(obj.get("volume")) if "volume" in obj else None,
            }
        )

    summary = {
        "status": result.get("status"),
        "agent_version": result.get("agent_version"),
        "project": result.get("project"),
        "session": result.get("session"),
        "run_id": result.get("run_id"),
        "run_number": result.get("run_number"),
        "started_at": result.get("started_at"),
        "finished_at": result.get("finished_at"),
        "current_dir": result.get("current_dir"),
        "output_dir": result.get("output_dir"),
        "document": {
            "name": document.get("name"),
            "label": document.get("label"),
            "object_count": document.get("object_count", 0),
            "visible_shape_count": len(visible_objects),
            "bounding_box": _compact_bounding_box(_union_bounding_box(object_source)),
            "objects": compact_objects,
        },
        "screenshots": [
            _screenshot_summary(item) for item in (result.get("screenshots") or [])
        ],
        "exports": result.get("exports") or {},
    }

    omitted = max(0, len(object_source) - max_objects)
    if omitted:
        summary["document"]["omitted_object_count"] = omitted
    if result.get("error"):
        summary["error"] = result.get("error")
    if result.get("traceback"):
        summary["traceback_tail"] = "\n".join(result.get("traceback", "").splitlines()[-12:])
    return summary


def _png_appears_blank(path, tolerance=8, min_changed_ratio=0.001):
    data = Path(path).read_bytes()
    if data[:8] != b"\x89PNG\r\n\x1a\n":
        return False

    pos = 8
    width = None
    height = None
    bit_depth = None
    color_type = None
    idat_chunks = []
    while pos + 8 <= len(data):
        length = struct.unpack(">I", data[pos : pos + 4])[0]
        kind = data[pos + 4 : pos + 8]
        chunk_start = pos + 8
        chunk_end = chunk_start + length
        chunk = data[chunk_start:chunk_end]
        pos = chunk_end + 4

        if kind == b"IHDR":
            width, height, bit_depth, color_type, _, _, _ = struct.unpack(
                ">IIBBBBB", chunk
            )
        elif kind == b"IDAT":
            idat_chunks.append(chunk)
        elif kind == b"IEND":
            break

    # FreeCAD saveImage normally writes 8-bit RGB PNGs. If another format appears,
    # do not block the screenshot; only use this as a best-effort blank detector.
    if not width or not height or bit_depth != 8 or color_type != 2:
        return False

    decompressed = zlib.decompress(b"".join(idat_chunks))
    bytes_per_pixel = 3
    stride = width * bytes_per_pixel
    previous = bytearray(stride)
    background = None
    changed = 0
    total = width * height
    offset = 0

    for _row_index in range(height):
        filter_type = decompressed[offset]
        offset += 1
        scanline = decompressed[offset : offset + stride]
        offset += stride
        reconstructed = bytearray(stride)

        for index, value in enumerate(scanline):
            left = (
                reconstructed[index - bytes_per_pixel]
                if index >= bytes_per_pixel
                else 0
            )
            up = previous[index]
            up_left = (
                previous[index - bytes_per_pixel] if index >= bytes_per_pixel else 0
            )
            if filter_type == 0:
                out = value
            elif filter_type == 1:
                out = (value + left) & 255
            elif filter_type == 2:
                out = (value + up) & 255
            elif filter_type == 3:
                out = (value + ((left + up) // 2)) & 255
            elif filter_type == 4:
                predictor = left + up - up_left
                pa = abs(predictor - left)
                pb = abs(predictor - up)
                pc = abs(predictor - up_left)
                predicted = (
                    left if pa <= pb and pa <= pc else up if pb <= pc else up_left
                )
                out = (value + predicted) & 255
            else:
                return False
            reconstructed[index] = out

        if background is None:
            background = tuple(reconstructed[0:bytes_per_pixel])

        for index in range(0, stride, bytes_per_pixel):
            pixel = tuple(reconstructed[index : index + bytes_per_pixel])
            delta = max(
                abs(pixel[channel] - background[channel]) for channel in range(3)
            )
            if delta > tolerance:
                changed += 1
                if float(changed) / float(total) >= min_changed_ratio:
                    return False

        previous = reconstructed

    return True


class FolderWatchAgent:
    def __init__(self, root):
        self.root = Path(root).resolve()
        self.inbox = self.root / "inbox"
        self.out = self.root / "out"
        self.logs = self.root / "logs"
        self.running = False
        self.current_job = None
        self.qtcore = _import_qtcore()
        self.timer = self.qtcore.QTimer()
        self.timer.timeout.connect(self.tick)

        for directory in (self.inbox, self.out, self.logs):
            directory.mkdir(parents=True, exist_ok=True)

    def start(self):
        self.timer.start(POLL_INTERVAL_MS)
        self._log(
            "Folder Watch Python Agent started. Watching: {}".format(self.inbox)
        )

    def stop(self):
        self.timer.stop()
        self._log("Folder Watch Python Agent stopped.")

    def tick(self):
        if self.running:
            return

        jobs = sorted(self.inbox.glob("*.json"), key=lambda path: path.stat().st_mtime)
        if not jobs:
            return

        job_path = jobs[0]
        running_path = job_path.with_suffix(".running")
        try:
            job_path.rename(running_path)
        except OSError:
            return

        self.running = True
        try:
            self._run_job(running_path)
        finally:
            self.running = False

    def _run_job(self, running_path):
        result = {
            "agent_version": BRIDGE_VERSION,
            "status": "running",
            "started_at": _now_iso(),
            "job_file": str(running_path),
        }

        try:
            job = json.loads(running_path.read_text(encoding="utf-8"))
            job_id = _safe_name(job.get("id") or running_path.stem)
            project = _project_id(job.get("project") or "default")
            session = _session_id(job.get("session") or "default")
            job["project"] = project
            job["session"] = session
            paths = self._job_paths(job, job_id)
            result["job"] = job
            result["job_id"] = job_id
            result["project"] = project
            result["session"] = session
            result["run_id"] = paths["run_id"]
            result["run_number"] = paths["run_number"]
            result["session_dir"] = str(paths["session_dir"])
            result["current_dir"] = str(paths["current_dir"])
        except Exception as exc:
            job_id = _safe_name(running_path.stem)
            result.update({"status": "error", "error": str(exc)})
            self._write_result(job_id, result, running_path, None)
            return

        job_out = paths["run_dir"]
        job_out.mkdir(parents=True, exist_ok=True)
        previous_doc_name = None
        if App.ActiveDocument is not None:
            previous_doc_name = App.ActiveDocument.Name

        try:
            self._log("Running job {}".format(job_id))
            doc = self._prepare_document(job)
            script_path = Path(job["script_path"]).expanduser().resolve()

            if not script_path.exists():
                raise FileNotFoundError("Script not found: {}".format(script_path))

            namespace = self._script_namespace(doc, job, job_out, script_path)
            code = script_path.read_text(encoding="utf-8")
            exec(compile(code, str(script_path), "exec"), namespace, namespace)

            if doc is not None:
                self._enforce_document_identity(doc, job)
                doc.recompute()
                self._refresh_gui_document(doc)

            exports = self._export_outputs(doc, job, job_out)
            if doc is not None:
                self._enforce_document_identity(doc, job)
                self._refresh_gui_document(doc)
            screenshots = self._capture_views(doc, job, job_out)

            if doc is not None:
                result["document"] = _document_info(doc)

            result.update(
                {
                    "status": "ok",
                    "finished_at": _now_iso(),
                    "output_dir": str(job_out),
                    "exports": exports,
                    "screenshots": screenshots,
                }
            )
        except Exception as exc:
            result.update(
                {
                    "status": "error",
                    "finished_at": _now_iso(),
                    "error": str(exc),
                    "traceback": traceback.format_exc(),
                }
            )
            self._log("Job {} failed: {}".format(job_id, exc))
        finally:
            if bool(job.get("restore_active_document", False)):
                self._restore_active_document(previous_doc_name)

        self._write_result(job_id, result, running_path, paths)

    def _job_paths(self, job, job_id):
        project = _project_id(job.get("project") or "default")
        session = _session_id(job.get("session") or "default")
        project_dir = self.out / "projects" / project
        session_dir = project_dir / "sessions" / session
        runs_dir = session_dir / "runs"
        runs_dir.mkdir(parents=True, exist_ok=True)

        run_number = self._next_run_number(runs_dir)
        run_label = _safe_name(
            job.get("job_title") or job.get("output_name") or job_id
        )
        timestamp = time.strftime("%Y%m%d-%H%M%S")
        run_id = "{:06d}-{}-{}".format(run_number, timestamp, run_label)
        run_dir = runs_dir / run_id
        while run_dir.exists():
            run_number += 1
            run_id = "{:06d}-{}-{}".format(run_number, timestamp, run_label)
            run_dir = runs_dir / run_id

        return {
            "project": project,
            "session": session,
            "project_dir": project_dir,
            "session_dir": session_dir,
            "runs_dir": runs_dir,
            "run_dir": run_dir,
            "current_dir": session_dir / "current",
            "run_id": run_id,
            "run_number": run_number,
        }

    def _next_run_number(self, runs_dir):
        highest = 0
        for path in runs_dir.iterdir():
            if not path.is_dir():
                continue
            prefix = path.name.split("-", 1)[0]
            try:
                highest = max(highest, int(prefix))
            except ValueError:
                pass
        return highest + 1

    def _prepare_document(self, job):
        project = _project_id(job.get("project") or "default")
        session = _session_id(job.get("session") or "default")
        doc_name = _freecad_internal_name(
            job.get("document_name") or "Agent_{}".format(session)
        )
        target_document = job.get("target_document", "session")
        mode = job.get("mode", "rebuild")
        doc_label = str(job.get("document_label") or doc_name)
        if target_document == "session":
            doc_name = _agent_document_name(project, session)
            doc_label = _agent_document_label(project, session)

        if target_document == "active":
            doc = App.ActiveDocument
            if doc is None:
                doc = App.newDocument(doc_name)
        elif target_document == "new":
            doc = App.newDocument(doc_name)
        else:
            doc = self._session_document(project, session)
            if doc is None:
                doc = App.newDocument(_agent_document_name(project, session))
            self._mark_session_document(doc, project, session)
            if mode != "update":
                self._clear_document(doc)

        doc.Label = doc_label
        if target_document == "session":
            self._mark_session_document(doc, project, session)
        elif target_document == "new":
            try:
                doc.Comment = "{}job={}".format(
                    AGENT_DOCUMENT_COMMENT_PREFIX, job.get("id", doc_name)
                )
            except Exception:
                pass

        try:
            App.setActiveDocument(doc.Name)
        except Exception:
            pass

        if Gui is not None and getattr(Gui, "ActiveDocument", None) is None:
            try:
                Gui.activeDocument()
            except Exception:
                pass

        self._enforce_document_identity(doc, job)
        return doc

    def _enforce_document_identity(self, doc, job):
        project = _project_id(job.get("project") or "default")
        session = _session_id(job.get("session") or "default")
        target_document = job.get("target_document", "session")
        if target_document != "session":
            return

        try:
            doc.Label = _agent_document_label(project, session)
        except Exception:
            pass
        self._mark_session_document(doc, project, session)

    def _session_document(self, project, session):
        marker = _session_marker(project, session)
        legacy_marker = _legacy_session_marker(session)
        for doc in App.listDocuments().values():
            try:
                if getattr(doc, "Comment", "") == marker:
                    return doc
                if project == "default" and getattr(doc, "Comment", "") == legacy_marker:
                    return doc
            except Exception:
                pass
        return None

    def _mark_session_document(self, doc, project, session):
        try:
            doc.Comment = _session_marker(project, session)
        except Exception:
            pass

    def _clear_document(self, doc):
        for obj in list(getattr(doc, "Objects", [])):
            try:
                doc.removeObject(obj.Name)
            except Exception:
                pass
        try:
            doc.recompute()
        except Exception:
            pass
        self._refresh_gui_document(doc)

    def _gui_document(self, doc):
        if Gui is None or doc is None:
            return None

        try:
            return Gui.getDocument(doc.Name)
        except Exception:
            try:
                App.setActiveDocument(doc.Name)
                self._process_events()
                return Gui.getDocument(doc.Name)
            except Exception:
                pass
        return None

    def _refresh_gui_document(self, doc):
        if Gui is None or doc is None:
            return

        try:
            App.setActiveDocument(doc.Name)
        except Exception:
            pass

        try:
            Gui.updateGui()
        except Exception:
            pass

        self._process_events()

    def _active_view_for_document(self, doc):
        for obj in getattr(doc, "Objects", []):
            try:
                return obj.ViewObject.Document.activeView()
            except Exception:
                pass

        gui_doc = self._gui_document(doc)
        if gui_doc is None:
            return None

        for method_name in ("activeView", "ActiveView"):
            try:
                view = getattr(gui_doc, method_name)
                if callable(view):
                    return view()
                return view
            except Exception:
                pass

        return None

    def _restore_active_document(self, doc_name):
        if not doc_name or doc_name not in App.listDocuments():
            return

        try:
            App.setActiveDocument(doc_name)
        except Exception:
            pass

        if Gui is not None:
            try:
                Gui.getDocument(doc_name)
            except Exception:
                pass

    def _script_namespace(self, doc, job, job_out, script_path):
        return {
            "__file__": str(script_path),
            "__name__": "__freecad_agent_job__",
            "App": App,
            "FreeCAD": App,
            "Gui": Gui,
            "FreeCADGui": Gui,
            "DOC": doc,
            "JOB": job,
            "OUT_DIR": job_out,
            "PARAMS": dict(job.get("params") or {}),
        }

    def _export_outputs(self, doc, job, job_out):
        if doc is None:
            return {}

        export_config = job.get("exports", {})
        base_name = _safe_name(job.get("output_name") or job.get("id") or doc.Name)
        exports = {}

        if export_config.get("fcstd", True):
            fcstd_path = job_out / "{}.FCStd".format(base_name)
            doc.saveAs(str(fcstd_path))
            exports["fcstd"] = str(fcstd_path)

        shape_objects = _shape_objects(doc, visible_only=True)

        if export_config.get("step", False) and shape_objects:
            step_path = job_out / "{}.step".format(base_name)
            try:
                import ImportGui

                ImportGui.export(shape_objects, str(step_path))
                exports["step"] = str(step_path)
            except Exception as exc:
                exports["step_error"] = str(exc)

        if export_config.get("stl", False) and shape_objects:
            stl_path = job_out / "{}.stl".format(base_name)
            try:
                import Mesh

                Mesh.export(shape_objects, str(stl_path))
                exports["stl"] = str(stl_path)
            except Exception as exc:
                exports["stl_error"] = str(exc)

        if export_config.get("3mf", False) and shape_objects:
            three_mf_path = job_out / "{}.3mf".format(base_name)
            try:
                import Mesh

                Mesh.export(shape_objects, str(three_mf_path))
                exports["3mf"] = str(three_mf_path)
            except Exception as exc:
                exports["3mf_error"] = str(exc)

        return exports

    def _capture_views(self, doc, job, job_out):
        screenshots = []
        if Gui is None or doc is None:
            return screenshots

        view_names = job.get("views")
        if view_names is None:
            view_names = ["iso", "front", "right", "top"]
        if not view_names:
            return screenshots
        width = int(job.get("screenshot_width", 1400))
        height = int(job.get("screenshot_height", 1000))
        background = job.get("screenshot_background", "White")
        views_dir = job_out / "views"
        views_dir.mkdir(parents=True, exist_ok=True)

        try:
            App.setActiveDocument(doc.Name)
        except Exception:
            pass
        self._process_events()

        for view_name in view_names:
            view_slug = _safe_name(view_name).lower()
            screenshot_path = views_dir / "{}.png".format(view_slug)
            try:
                active_view = self._active_view_for_document(doc)
                if active_view is None:
                    raise RuntimeError("No GUI view available for {}".format(doc.Name))
                self._set_view(active_view, view_slug)
                self._process_events()
                active_view.saveImage(str(screenshot_path), width, height, background)
                if self._screenshot_appears_blank(screenshot_path):
                    self._log(
                        "Screenshot {} appears blank; retrying view fit".format(
                            screenshot_path
                        )
                    )
                    self._set_view(active_view, view_slug, retry=True)
                    self._process_events()
                    active_view.saveImage(
                        str(screenshot_path), width, height, background
                    )
                    if self._screenshot_appears_blank(screenshot_path):
                        raise RuntimeError(
                            "{} screenshot appears blank after retry".format(view_slug)
                        )
                screenshots.append(str(screenshot_path))
            except Exception as exc:
                screenshots.append(
                    {"view": view_slug, "path": str(screenshot_path), "error": str(exc)}
                )

        return screenshots

    def _set_view(self, active_view, view_name, retry=False):
        method_names = {
            "iso": "viewIsometric",
            "isometric": "viewIsometric",
            "front": "viewFront",
            "rear": "viewRear",
            "back": "viewRear",
            "right": "viewRight",
            "left": "viewLeft",
            "top": "viewTop",
            "bottom": "viewBottom",
        }
        method = method_names.get(view_name, "viewIsometric")
        getattr(active_view, method)()
        self._process_events()
        try:
            Gui.updateGui()
        except Exception:
            pass
        try:
            active_view.fitAll()
        except Exception:
            pass
        self._process_events()
        try:
            Gui.SendMsgToActiveView("ViewFit")
        except Exception:
            pass
        self._process_events()
        try:
            active_view.fitAll()
        except Exception:
            pass
        if retry:
            self._process_events()
            try:
                active_view.fitAll()
            except Exception:
                pass

    def _screenshot_appears_blank(self, path):
        try:
            return _png_appears_blank(path)
        except Exception as exc:
            self._log("Could not inspect screenshot {}: {}".format(path, exc))
            return False

    def _process_events(self):
        try:
            self.qtcore.QCoreApplication.processEvents()
        except Exception:
            pass
        time.sleep(0.2)

    def _write_result(self, job_id, result, running_path, paths):
        if paths is None:
            job_out = self.out / "errors" / job_id
        else:
            job_out = paths["run_dir"]

        job_out.mkdir(parents=True, exist_ok=True)
        result["output_dir"] = str(job_out)
        result_path = job_out / "result.json"
        _write_json(result_path, result)
        _write_json(job_out / "result_summary.json", _result_summary(result))

        try:
            shutil.move(str(running_path), str(job_out / "job.json"))
        except Exception:
            pass

        if paths is not None:
            self._sync_current(paths["run_dir"], paths["current_dir"])
            self._update_metadata(paths, result)
            self._append_session_index(paths, result)

            session_latest = paths["session_dir"] / "latest_result.json"
            project_latest = paths["project_dir"] / "latest_result.json"
            _write_json(session_latest, result)
            _write_json(project_latest, result)
            _write_json(
                paths["session_dir"] / "latest_result_summary.json",
                _result_summary(result),
            )
            _write_json(
                paths["project_dir"] / "latest_result_summary.json",
                _result_summary(result),
            )

        latest_path = self.out / "latest_result.json"
        _write_json(latest_path, result)
        _write_json(self.out / "latest_result_summary.json", _result_summary(result))

        self._log("Finished job {} with status {}".format(job_id, result["status"]))

    def _sync_current(self, run_dir, current_dir):
        tmp_current = current_dir.with_name("current.tmp")
        try:
            if tmp_current.exists():
                shutil.rmtree(str(tmp_current))
            shutil.copytree(str(run_dir), str(tmp_current))
            if current_dir.exists():
                shutil.rmtree(str(current_dir))
            tmp_current.rename(current_dir)
        except Exception as exc:
            self._log("Could not update current output: {}".format(exc))

    def _update_metadata(self, paths, result):
        now = result.get("finished_at") or _now_iso()
        project_meta_path = paths["project_dir"] / "project.json"
        project_meta = _read_json(project_meta_path, {})
        project_meta.setdefault("id", paths["project"])
        project_meta.setdefault("created_at", now)
        project_meta["updated_at"] = now
        project_meta["latest_session"] = paths["session"]
        project_meta["latest_run"] = paths["run_id"]
        _write_json(project_meta_path, project_meta)

        session_meta_path = paths["session_dir"] / "session.json"
        session_meta = _read_json(session_meta_path, {})
        session_meta.setdefault("project", paths["project"])
        session_meta.setdefault("id", paths["session"])
        session_meta.setdefault("created_at", now)
        session_meta["updated_at"] = now
        session_meta["current_run"] = paths["run_id"]
        session_meta["current_result"] = str(paths["current_dir"] / "result.json")
        session_meta["latest_status"] = result.get("status")
        session_meta["run_count"] = self._count_run_dirs(paths["runs_dir"])
        _write_json(session_meta_path, session_meta)

    def _append_session_index(self, paths, result):
        summary = {
            "job_id": result.get("job_id"),
            "run_id": paths["run_id"],
            "run_number": paths["run_number"],
            "project": paths["project"],
            "session": paths["session"],
            "status": result.get("status"),
            "started_at": result.get("started_at"),
            "finished_at": result.get("finished_at"),
            "output_dir": str(paths["run_dir"]),
            "current_dir": str(paths["current_dir"]),
            "job_title": (result.get("job") or {}).get("job_title"),
        }
        _append_jsonl(paths["session_dir"] / "index.jsonl", summary)

    def _count_run_dirs(self, runs_dir):
        try:
            return len([path for path in runs_dir.iterdir() if path.is_dir()])
        except Exception:
            return 0

    def _log(self, message):
        line = "[{}] {}\n".format(time.strftime("%Y-%m-%d %H:%M:%S"), message)
        try:
            with (self.logs / "freecad_folder_watch_agent.log").open(
                "a", encoding="utf-8"
            ) as log_file:
                log_file.write(line)
        except Exception:
            pass
        try:
            App.Console.PrintMessage(line)
        except Exception:
            sys.stdout.write(line)


try:
    if hasattr(App, "_folder_watch_agent"):
        App._folder_watch_agent.stop()
except Exception:
    pass

FOLDER_WATCH_AGENT = FolderWatchAgent(_macro_root())
App._folder_watch_agent = FOLDER_WATCH_AGENT
FOLDER_WATCH_AGENT.start()
